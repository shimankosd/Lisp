(defun getcolor	()   ; “становка цвет из меню автокада\ acad_dev.
  (setq num_color (atoi (getvar "cecolor")))
  (setq num_color (acad_colordlg num_color))
  (command "color" num_color)
)

(setq specify_a 100)
(setq specify_b 100)

(defun getpt ()   ; „лЯ координат с мыши.
  (setq pt (getpoint "\n “кажите точку"))
  (setq specify_x (rtos (car pt) 2 3))    ; RTOS преобразует лист в стр
  (setq specify_y (rtos (cadr pt) 2 3))
  (setq specify_a (car pt))    
  (setq specify_b (cadr pt))
)

  (defun res_func()
    (setq p0 (strcat (rtos specify_a 2 3) "," (rtos specify_b 2 3)))
    (setq p1 (strcat (rtos (+ specify_a (* 30 k)) 2 3) "," (rtos (+ specify_b (* 20 k)) 2 3)))
    (setq p2 (strcat (rtos specify_a 2 3) "," (rtos (+ specify_b (* 10 k)) 2 3)))
    (setq p3 (strcat (rtos (- specify_a (* 20 k)) 2 3) "," (rtos (+ specify_b (* 10 k)) 2 3)))
    (setq p4 (strcat (rtos (+ specify_a (* 30 k)) 2 3) "," (rtos (+ specify_b (* 10 k)) 2 3)))
    (setq p5 (strcat (rtos (+ specify_a (* 50 k)) 2 3) "," (rtos (+ specify_b (* 10 k)) 2 3)))
    (command "rectangle" p0 p1)
    (command "line" p2 p3 "")
    (command "line" p4 p5 "")
    (setq w_n 0)
  )

  (defun diod_func()
    (setq p6 (strcat (rtos specify_a 2 3) "," (rtos specify_b 2 3)))
    (setq p7 (strcat (rtos specify_a 2 3) "," (rtos (+ specify_b (* 22 k)) 2 3)))
    (setq p8 (strcat (rtos (+ specify_a (* 19 k)) 2 3) "," (rtos (+ specify_b (* 22 k)) 2 3)))
    (setq p9 (strcat (rtos (- specify_a (* 19 k)) 2 3) "," (rtos (+ specify_b (* 22 k)) 2 3)))
    (setq p10 (strcat (rtos specify_a 2 3) "," (rtos (- specify_b (* 11 k)) 2 3)))
    (setq p11 (strcat (rtos specify_a 2 3) "," (rtos (- specify_b (* 44 k)) 2 3)))
    (setq p12 (strcat (rtos specify_a 2 3) "," (rtos (+ specify_b (* 22 k)) 2 3)))
    (setq p13 (strcat (rtos specify_a 2 3) "," (rtos (+ specify_b (* 55 k)) 2 3)))
	(setq kd (* 22 k))
    (command "polygon" "3" p6 "i" kd)
    (command "line" p7 p8 "")
    (command "line" p7 p9 "")
    (command "line" p10 p11 "")
    (command "line" p12 p13 "")
    (setq w_n 0)
  )

  (defun con_func()
    (setq p14 (strcat (rtos specify_a 2 3) "," (rtos specify_b 2 3)))
    (setq p15 (strcat (rtos (+ specify_a (* 33 k)) 2 3) "," (rtos specify_b 2 3)))
    (setq p16 (strcat (rtos (+ specify_a (* 33 k)) 2 3) "," (rtos (+ specify_b (* 17 k)) 2 3)))
    (setq p17 (strcat (rtos (+ specify_a (* 33 k)) 2 3) "," (rtos (- specify_b (* 17 k)) 2 3)))
    (setq p18 (strcat (rtos (+ specify_a (* 38 k)) 2 3) "," (rtos specify_b 2 3)))
    (setq p19 (strcat (rtos (+ specify_a (* 38 k)) 2 3) "," (rtos (+ specify_b (* 17 k)) 2 3)))
    (setq p20 (strcat (rtos (+ specify_a (* 38 k)) 2 3) "," (rtos (- specify_b (* 17 k)) 2 3)))
    (setq p21 (strcat (rtos (+ specify_a (* 71 k)) 2 3) "," (rtos specify_b 2 3)))
    (command "line" p14 p15 "")
    (command "line" p15 p16 "")
    (command "line" p15 p17 "")
    (command "line" p18 p19 "")
    (command "line" p18 p20 "")
    (command "line" p18 p21 "")
    (setq w_n 0)
  )

 (defun ist_func()
    (setq pc (strcat (rtos specify_a 2 3) "," (rtos specify_b 2 3)))
	(setq ci (* 22 k))
    (command "circle" pc ci)
    (setq p23 (strcat (rtos (- specify_a (* 22 k)) 2 3) "," (rtos specify_b 2 3)))
    (setq p24 (strcat (rtos (- specify_a (* 55 k)) 2 3) "," (rtos specify_b 2 3)))
    (command "line" p23 p24 "")
    (setq p25 (strcat (rtos (+ specify_a (* 22 k)) 2 3) "," (rtos specify_b 2 3)))
    (setq p26 (strcat (rtos (+ specify_a (* 55 k)) 2 3) "," (rtos specify_b 2 3)))
    (command "line" p25 p26 "")
    (command "line" p23 p25 "")
    (setq p27 (strcat (rtos (+ specify_a (* 11 k)) 2 3) "," (rtos (+ specify_b (* 11 k)) 2 3)))
    (setq p28 (strcat (rtos (+ specify_a (* 11 k)) 2 3) "," (rtos (- specify_b (* 11 k)) 2 3)))
    (command "line" p27 p25 "")
    (command "line" p28 p25 "")
    (setq w_n 0)
  )

  (defun tran_func()
    (setq p29 (strcat (rtos specify_a 2 3) "," (rtos specify_b 2 3)))
	(setq ct (* 22 k))
    (command "circle" p29 ct)
    (setq p30 (strcat (rtos (- specify_a (* 7 k)) 2 3) "," (rtos (- specify_b (* 12 k)) 2 3)))
    (setq p31 (strcat (rtos (- specify_a (* 7 k)) 2 3) "," (rtos (+ specify_b (* 12 k)) 2 3)))
    (command "line" p30 p31 "")
    (setq p32 (strcat (rtos (- specify_a (* 7 k)) 2 3) "," (rtos specify_b 2 3)))
    (setq p33 (strcat (rtos (- specify_a (* 40 k)) 2 3) "," (rtos specify_b 2 3)))
    (command "line" p32 p33 "")
    (setq p34 (strcat (rtos (- specify_a (* 7 k)) 2 3) "," (rtos (- specify_b (* 9 k)) 2 3)))
    (setq p35 (strcat (rtos (- specify_a (* 7 k)) 2 3) "," (rtos (+ specify_b (* 9 k)) 2 3)))
    (setq p36 (strcat (rtos specify_a 2 3) "," (rtos (- specify_b (* 22 k)) 2 3)))
    (setq p37 (strcat (rtos specify_a 2 3) "," (rtos (+ specify_b (* 22 k)) 2 3)))
    (command "line" p34 p36 "")
    (command "line" p35 p37 "")
    (setq p38 (strcat (rtos specify_a 2 3) "," (rtos (- specify_b (* 40 k)) 2 3)))
    (setq p39 (strcat (rtos specify_a 2 3) "," (rtos (+ specify_b (* 40 k)) 2 3)))
    (command "line" p36 p38 "")
    (command "line" p37 p39 "")
    (setq p40 (strcat (rtos (- specify_a (* 6.2 k) ) 2 3) "," (rtos (- specify_b (* 13 k)) 2 3)))
    (setq p41 (strcat (rtos (- specify_a (* 4.23 k)) 2 3) "," (rtos (- specify_b (* 12 k)) 2 3)))
    (command "line" p34 p40 "")
    (command "line" p34 p41 "")
    (setq w_n 0)
  )

  



(defun main_dialog ()
  (if (not (new_dialog "cc" dcl_id)) (exit))

  (start_image "res")(slide_image 0 -12 (dimx_tile "res") (dimy_tile "res") "d:\\lab\\Resistor")(end_image)
  (start_image "diod")(slide_image 3 -15 (dimx_tile "diod") (dimy_tile "diod") "d:\\lab\\Diod")(end_image)
  (start_image "con")(slide_image 5 -15 (dimx_tile "con") (dimy_tile "con") "d:\\lab\\Condensator")(end_image)
  (start_image "ist")(slide_image 5 -15 (dimx_tile "ist") (dimy_tile "ist") "d:\\lab\\Istochnik")(end_image)
  (start_image "tran")(slide_image 3 -15 (dimx_tile "tran") (dimy_tile "tran") "d:\\lab\\Transistor")(end_image)
  (start_image "specify_color")(fill_image 0 0 500 500 (atoi (getvar "cecolor")))(end_image)

  (set_tile "specify_x" specify_x)
  (set_tile "specify_y" specify_y)

  
  (action_tile "button_Cancel" "(setq w_n 0)")
  (action_tile "button_color" "(done_dialog 3)")
  (action_tile "specify_color" "(done_dialog 3)")
  (action_tile "specify_the_mouse" "(done_dialog 4)")
  (action_tile "specify_x" "(setq specify_x $value)")
  (action_tile "specify_y" "(setq specify_y $value)")
  (action_tile "dimensions" "(done_dialog 5)")
  (action_tile "res" "(done_dialog 7)")
  (action_tile "diod" "(done_dialog 6)")
  (action_tile "con" "(done_dialog 8)")
  (action_tile "ist" "(done_dialog 9)")
  (action_tile "tran" "(done_dialog 10)")
  
  (setq specify_a (atoi specify_x))
  (setq specify_b (atoi specify_y))
  
  
  (setq w_n (start_dialog))   ; срабатывание функций при нажатии определенных кнопок.
  (if (= w_n 3) (getcolor))
  (if (= w_n 4) (getpt))
  (if (= w_n 6) (diod_func))
  (if (= w_n 7) (res_func))
  (if (= w_n 8) (con_func))
  (if (= w_n 9) (ist_func))
  (if (= w_n 10) (tran_func))
  (while (= w_n 5) (dimension_dialog))
)


(defun dimension_dialog ()   ; „лЯ окошка с масшатбом.
  (if (not (new_dialog "Dimensions" dcl_id)) (exit))
  
  (action_tile "accept" "(done_dialog 2)")

  (action_tile "m1" "(setq k 1)")
  (action_tile "m2" "(setq k 1.5)")
  (action_tile "m3" "(setq k 2)")
  
  (setq w_n (start_dialog))
  (if (= w_n 2) (main_dialog))
)

(defun c:cc ()  ; подгрузка dcl и установка начальных значений.
  (setq w_n 2 specify_x "0" specify_y "0")  
  (setq dcl_id (load_dialog "d:\\lab\\cc.dcl"))
  (while (> w_n 0) (main_dialog))
  (unload_dialog dcl_id)
)
